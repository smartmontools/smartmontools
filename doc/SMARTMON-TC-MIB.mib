SMARTMON-TC-MIB DEFINITIONS ::= BEGIN

IMPORTS
    MODULE-IDENTITY, Integer32, Unsigned32, Counter64, OBJECT-TYPE, enterprises
        FROM SNMPv2-SMI
    TEXTUAL-CONVENTION
        FROM SNMPv2-TC;

-- Root OID for all SMARTMON-*-MIB modules
smartmonRoot OBJECT IDENTIFIER ::= { enterprises 9999 1 1 }

smartmonTcMIB MODULE-IDENTITY
    LAST-UPDATED "202605210000Z"
    ORGANIZATION "Unassigned"
    CONTACT-INFO
        "This is a draft MIB for smartmontools smartctl output.

         TODO: Replace the placeholder enterprise OID before publication."
    DESCRIPTION
        "Textual conventions shared across all SMARTMON-*-MIB modules."
    REVISION "202605210000Z"
    DESCRIPTION
        "Added SmartmonAtaApmLevel. Added SmartmonLogicalBlockAddress.
         Added SmartmonAtaMinorVersion (named INTEGER, word-81 values).
         Added SmartmonAtaLogAddress (GetLogName), SmartmonAtaDevStatPage
         (device statistics page numbers), SmartmonAtaOfflineStatus
         (offline collection status bits 6:0).
         Fixed SmartmonAtaSelfTestType: replaced unknown(0)/abort(9) with
         offline(0)/abortOffline(127); added captive variants 129-132.
         Removed unused neverRun(255) from SmartmonAtaSelfTestResult."
    REVISION "202605180000Z"
    DESCRIPTION "Initial draft."
    ::= { smartmonRoot 1 }

-- --------------------------------------------------------------------------
-- Textual conventions
-- --------------------------------------------------------------------------

SmartmonDeviceType ::= TEXTUAL-CONVENTION
    STATUS      current
    DESCRIPTION
        "Device or transport family as reported or selected for smartctl."
    SYNTAX INTEGER {
        unknown(0),
        ata(1),
        sat(2),
        scsi(3),
        sas(4),
        nvme(5),
        usbBridge(6),
        megaraid(7),
        cciss(8),
        areca(9),
        other(255)
    }

SmartmonHealthStatus ::= TEXTUAL-CONVENTION
    STATUS      current
    DESCRIPTION
        "Normalized health status derived from smartctl output."
    SYNTAX INTEGER {
        unknown(0),
        passed(1),
        failed(2),
        warning(3),
        unavailable(4)
    }

SmartmonPollResult ::= TEXTUAL-CONVENTION
    STATUS      current
    DESCRIPTION
        "Result of the last smartctl collection attempt."
    SYNTAX INTEGER {
        unknown(0),
        ok(1),
        failed(2),
        timeout(3),
        permissionDenied(4),
        unsupported(5),
        parseError(6)
    }

SmartmonPercentage ::= TEXTUAL-CONVENTION
    DISPLAY-HINT "d"
    STATUS      current
    DESCRIPTION
        "Percentage value.  NVMe Percentage Used can exceed 100 per the
         NVMe specification, so the range is intentionally wider than
         0..100."
    SYNTAX Unsigned32 (0..4294967295)

SmartmonNvmeSelfTestResult ::= TEXTUAL-CONVENTION
    STATUS      current
    DESCRIPTION
        "Normalized NVMe self-test result code."
    SYNTAX INTEGER {
        unknown(0),
        completedWithoutError(1),
        abortedByHost(2),
        interruptedByControllerReset(3),
        failedUnknownSegment(4),
        failedKnownSegment(5),
        abortedUnknownReason(6),
        abortedSanitizeOperation(7),
        noSelfTestInProgress(8),
        inProgress(9),
        vendorSpecific(255)
    }

SmartmonAtaSelfTestResult ::= TEXTUAL-CONVENTION
    STATUS      current
    DESCRIPTION
        "Normalized ATA/SATA self-test result derived from the status
         nibble of the Self-test execution status byte."
    SYNTAX INTEGER {
        unknown(0),
        completedWithoutError(1),
        abortedByHost(2),
        interruptedByReset(3),
        fatalOrUnknownFailure(4),
        completedUnknownFailure(5),
        completedElectricalFailure(6),
        completedServomechanismFailure(7),
        completedReadFailure(8),
        completedHandlingDamageSuspect(9),
        inProgress(15)
    }

SmartmonAtaSelfTestType ::= TEXTUAL-CONVENTION
    STATUS      current
    DESCRIPTION
        "The type of self-test recorded in an ATA/SATA self-test log
         entry, as the raw self-test routine byte from the log.
         Bit 7 (0x80) distinguishes captive (foreground) from offline
         (background) mode.  Values 0x40-0x7e and 0x90+ are
         vendor-specific and will appear as unrecognised integers."
    SYNTAX INTEGER {
        offline(0),
        short(1),
        extended(2),
        conveyance(3),
        selective(4),
        abortOffline(127),
        shortCaptive(129),
        extendedCaptive(130),
        conveyanceCaptive(131),
        selectiveCaptive(132)
    }

SmartmonNvmeSelfTestType ::= TEXTUAL-CONVENTION
    STATUS      current
    DESCRIPTION
        "The type of self-test recorded in an NVMe self-test log
         entry, derived from the Self-test Action field."
    SYNTAX INTEGER {
        unknown(0),
        short(1),
        extended(2),
        vendorSpecific(255)
    }

SmartmonSasSelfTestType ::= TEXTUAL-CONVENTION
    STATUS      current
    DESCRIPTION
        "The type of self-test recorded in a SAS/SCSI self-test log
         entry, derived from the self-test code field."
    SYNTAX INTEGER {
        unknown(0),
        backgroundShort(1),
        backgroundExtended(2),
        foregroundShort(3),
        foregroundExtended(4)
    }

SmartmonAtaSmartAttrType ::= TEXTUAL-CONVENTION
    STATUS      current
    DESCRIPTION
        "ATA SMART attribute type derived from the prefailure flag."
    SYNTAX INTEGER {
        unknown(0),
        prefailure(1),
        oldAge(2)
    }

SmartmonAtaSmartAttrUpdated ::= TEXTUAL-CONVENTION
    STATUS      current
    DESCRIPTION
        "Whether an ATA SMART attribute is updated continuously (always)
         or only during offline data collection (offline)."
    SYNTAX INTEGER {
        unknown(0),
        always(1),
        offline(2)
    }

SmartmonAtaSmartAttrStatus ::= TEXTUAL-CONVENTION
    STATUS      current
    DESCRIPTION
        "Failure status of an ATA SMART attribute derived from its
         normalized value, worst value, and failure threshold.
         notRelevant(-1) -- threshold is 0; no failure threshold defined
         unknown(0)      -- status cannot be determined
         ok(1)           -- value is above the failure threshold
         failing  Now(2)   -- value is at or below the threshold (prefailure)
         failed In Past(3) -- worst value was ever at or below the threshold"
    SYNTAX INTEGER {
        notRelevant(-1),
        unknown(0),
        ok(1),
        failingNow(2),
        failedInPast(3)
    }

SmartmonAtaFormFactor ::= TEXTUAL-CONVENTION
    STATUS      current
    DESCRIPTION
        "ATA drive form factor derived from IDENTIFY DEVICE word 168 bits 3:0
         (form_factor.ata_value).  unknown(0) indicates the field is not
         reported or reserved."
    SYNTAX INTEGER {
        unknown(0),
        inches525(1),
        inches35(2),
        inches25(3),
        inches18(4),
        lessThan18Inches(5),
        mSata(6),
        m2(7),
        microSsd(8),
        cFast(9)
    }

SmartmonSataVersion ::= TEXTUAL-CONVENTION
    STATUS      current
    DESCRIPTION
        "SATA version derived from the most-significant set bit of bits
         11:0 of IDENTIFY DEVICE word 222 (sata_version.value).
         unknown(0) indicates the field is 0x0000 or 0xffff (not
         reported).  Values are offset by one from the bit position so
         that unknown(0) is unambiguous: ata8Ast(1) is bit 0, sata10a(2)
         is bit 1, and so on."
    SYNTAX INTEGER {
        unknown(0),
        ata8Ast(1),
        sata10a(2),
        sataIiExt(3),
        sata25(4),
        sata26(5),
        sata30(6),
        sata31(7),
        sata32(8),
        sata33(9),
        sata34(10),
        sata35(11),
        sataAbove35(12)
    }

SmartmonAtaDeviceState ::= TEXTUAL-CONVENTION
    STATUS      current
    DESCRIPTION
        "Device state nibble from an ATA error log entry
         (device_state.value & 0x0f).  Values 5..10 are reserved by the
         ATA specification; values 11..15 are vendor-specific."
    SYNTAX INTEGER {
        unknown(0),
        sleeping(1),
        standby(2),
        activeOrIdle(3),
        smartOfflineOrSelftest(4)
    }

SmartmonAtaMinorVersion ::= TEXTUAL-CONVENTION
    STATUS      current
    DESCRIPTION
        "ATA minor version number from IDENTIFY DEVICE word 81
         (ata_version.minor_value).  0x0000 (0) and 0xffff (65535)
         indicate not reported.  Values are sparse; unlisted integers
         are reserved or vendor-specific.
         Source: ataprint.cpp get_ata_minor_version."
    SYNTAX INTEGER {
        ata1X3t9Pr4(1),
        ata1Ansi1994(2),
        ata1X3t9Rev4(3),
        ata2Ansi1996(4),
        ata2X3t10Pr2k(5),
        ata3X3t10Rev1(6),
        ata2X3t10Rev2k(7),
        ata3X3t10Rev0(8),
        ata2X3t10Rev3(9),
        ata3Ansi1997(10),
        ata3X3t10Rev6(11),
        ata3X3t13Rev7(12),
        ataAtapi4X3t13Rev6(13),
        ataAtapi4T13Rev13(14),
        ataAtapi4X3t13Rev7(15),
        ataAtapi4T13Rev18(16),
        ataAtapi4T13Rev15(17),
        ataAtapi4Ansi1998(18),
        ataAtapi5T13Rev3(19),
        ataAtapi4T13Rev14(20),
        ataAtapi5T13Rev1(21),
        ataAtapi5Ansi2000(22),
        ataAtapi4T13Rev17(23),
        ataAtapi6T13Rev0(24),
        ataAtapi6T13Rev3a(25),
        ataAtapi7T13Rev1(26),
        ataAtapi6T13Rev2(27),
        ataAtapi6T13Rev1(28),
        ataAtapi7Ansi2005(29),
        ataAtapi7T13Rev0(30),
        acs3T13Rev3b(31),
        ataAtapi7T13Rev4a(33),
        ataAtapi6Ansi2002(34),
        acs6BsrRev7(37),
        ata8AcsRev3c(39),
        ata8AcsRev6(40),
        ata8AcsRev4(41),
        acs5BsrRev10(48),
        acs2T13Rev2(49),
        ata8AcsRev3e(51),
        ata8AcsRev4c(57),
        ata8AcsRev3f(66),
        ata8AcsRev3b(82),
        acs4BsrRev5(94),
        acs3T13Rev5(109),
        acs6BsrRev11(112),
        acs6BsrRev2(115),
        acs2Ansi2012(130),
        acs4Ansi2018(156),
        ata8AcsRev2d(263),
        acs3Ansi2014(266),
        acs2T13Rev3(272),
        acs3T13Rev4(283)
    }

SmartmonAtaVersion ::= TEXTUAL-CONVENTION
    STATUS      current
    DESCRIPTION
        "ATA/ACS major version derived from the most-significant set bit
         of IDENTIFY DEVICE word 80 (ata_version.major_value).
         unknown(0) indicates the field is 0x0000 or 0xffff (not reported)."
    SYNTAX INTEGER {
        unknown(0),
        ata1(1),
        ata2(2),
        ata3(3),
        ataAtapi4(4),
        ataAtapi5(5),
        ataAtapi6(6),
        ataAtapi7(7),
        ata8Acs(8),
        acs2(9),
        acs3(10),
        acs4(11),
        acs5(12),
        acs6(13),
        acsAbove6(14)
    }

SmartmonAtaApmLevel ::= TEXTUAL-CONVENTION
    STATUS      current
    DESCRIPTION
        "ATA Advanced Power Management (APM) level (ata_apm.level).
         Named values mark the boundary points of each band; all integers
         within a band are valid and meaningful.

         From hdparm(8): A low value means aggressive power management
         and a high value means better performance.  Possible settings
         range from values 1 through 127 (which permit spin-down), and
         values 128 through 254 (which do not permit spin-down).  The
         highest degree of power management is attained with a setting
         of 1, and the highest I/O performance with a setting of 254.
         A value of 255 tells hdparm to disable Advanced Power Management
         altogether on the drive (not all drives support disabling it,
         but most do).

         Value 0 indicates APM is not reported by the drive."
    SYNTAX INTEGER {
        notReported(0),
        minimumPower(1),
        intermediateSpinDownLow(2),
        intermediateSpinDownHigh(127),
        intermediateNoSpinDownLow(128),
        maximumPerformance(254),
        apmDisabled(255)
    }

SmartmonAtaLogAddress ::= TEXTUAL-CONVENTION
    STATUS      current
    DESCRIPTION
        "ATA GPL/SMART log address as reported in the Log Directory
         (ata_smart_log_directory / gp_log_directory table[].address).
         Source: ataprint.cpp GetLogName.
         Values 0x1a-0x1f, 0x26-0x2e, 0x31-0x41, 0x43-0x46,
         0x48-0x52, 0x54-0x58, 0x5a-0x60, 0x62-0x7f are reserved.
         All integers in hostVendorSpecificFirst(128)..hostVendorSpecificLast(159)
         are host vendor specific logs.
         All integers in deviceVendorSpecificFirst(160)..deviceVendorSpecificLast(223)
         are device vendor specific logs.
         Values 0xe2-0xff are reserved."
    SYNTAX INTEGER {
        logDirectory(0),
        summarySmartErrorLog(1),
        comprehensiveSmartErrorLog(2),
        extComprehensiveSmartErrorLog(3),
        deviceStatisticsLog(4),
        reservedForCfa1(5),
        smartSelfTestLog(6),
        extendedSelfTestLog(7),
        powerConditionsLog(8),
        selectiveSelfTestLog(9),
        deviceStatisticsNotification(10),
        reservedForCfa2(11),
        pendingDefectsLog(12),
        lpsMisalignmentLog(13),
        reservedForZac2(14),
        senseDataForNcqLog(15),
        ncqCommandErrorLog(16),
        sataPhyEventCountersLog(17),
        sataNcqNonDataLog(18),
        sataNcqSendReceiveLog(19),
        hybridInformationLog(20),
        rebuildAssistLog(21),
        outOfBandMgmtLog(22),
        reservedForSata(23),
        commandDurationLimitsLog(24),
        lbaStatusLog(25),
        streamingPerformanceLog(32),
        writeStreamErrorLog(33),
        readStreamErrorLog(34),
        delayedSectorLog(35),
        currentDeviceInternalStatus(36),
        savedDeviceInternalStatus(37),
        sectorConfigLog(47),
        identifyDeviceDataLog(48),
        mutateConfigurationsLog(66),
        concurrentPositioningRangesLog(71),
        senseDataLog(83),
        powerConsumptionControlLog(89),
        capacityModelNumberMappingLog(97),
        hostVendorSpecificFirst(128),
        hostVendorSpecificLast(159),
        deviceVendorSpecificFirst(160),
        deviceVendorSpecificLast(223),
        sctCommandStatus(224),
        sctDataTransfer(225)
    }

SmartmonAtaDevStatPage ::= TEXTUAL-CONVENTION
    STATUS      current
    DESCRIPTION
        "ATA Device Statistics log page number
         (ata_device_statistics.pages[].number).
         Source: ataprint.cpp get_device_statistics_page_name / devstat_infos."
    SYNTAX INTEGER {
        supportedLogPages(0),
        generalStatistics(1),
        freeFallStatistics(2),
        rotatingMediaStatistics(3),
        generalErrorsStatistics(4),
        temperatureStatistics(5),
        transportStatistics(6),
        solidStateStatistics(7),
        vendorSpecific(255)
    }

SmartmonAtaOfflineStatus ::= TEXTUAL-CONVENTION
    STATUS      current
    DESCRIPTION
        "ATA offline data collection status derived from bits 6:0 of the
         status byte (ata_smart_data.offline_data_collection.status.value).
         Bit 7 of the raw byte is the Auto Offline Data Collection flag
         and is not represented here.  Source: ataprint.cpp
         OfflineDataCollectionStatus.  Values 0x01, 0x07-0x3f are
         reserved; 0x40-0x7f are vendor-specific."
    SYNTAX INTEGER {
        neverStarted(0),
        completedWithoutError(2),
        inProgress(3),
        suspendedByCommand(4),
        abortedByCommand(5),
        abortedFatalError(6)
    }

SmartmonScsiErrorDirection ::= TEXTUAL-CONVENTION
    STATUS      current
    DESCRIPTION
        "I/O direction for SAS/SCSI error counter log rows."
    SYNTAX INTEGER {
        read(1),
        write(2),
        verify(3)
    }

-- --------------------------------------------------------------------------
-- Sensor textual conventions  (mirroring ENTITY-SENSOR-MIB RFC 3433)
-- --------------------------------------------------------------------------

SmartmonSensorDataType ::= TEXTUAL-CONVENTION
    STATUS      current
    DESCRIPTION
        "The physical quantity measured by a sensor row in
         smartmonSensorTable.  Together with SmartmonSensorDataScale and
         SmartmonSensorPrecision it fully determines the unit of the
         associated SmartmonSensorValue."
    REFERENCE "RFC 3433, EntitySensorDataType"
    SYNTAX INTEGER {
        other(1),
        unknown(2),
        celsius(3),
        watts(4),
        amperes(5),
        voltsDC(6),
        voltsAC(7),
        vibration(8),
        rpm(9),
        percent(10)
    }

SmartmonSensorDataScale ::= TEXTUAL-CONVENTION
    STATUS      current
    DESCRIPTION
        "SI prefix scaling factor for a sensor value.  An object of this
         type SHOULD be examined together with the associated
         SmartmonSensorPrecision and SmartmonSensorValue objects to
         determine the true measurement.

         Example: milliwatts uses scale milli(8), precision 0."
    REFERENCE "RFC 3433, EntitySensorDataScale"
    SYNTAX INTEGER {
        yocto(1),    -- 10^-24
        zepto(2),    -- 10^-21
        atto(3),     -- 10^-18
        femto(4),    -- 10^-15
        pico(5),     -- 10^-12
        nano(6),     -- 10^-9
        micro(7),    -- 10^-6
        milli(8),    -- 10^-3
        units(9),    -- 10^0
        kilo(10),    -- 10^3
        mega(11),    -- 10^6
        giga(12),    -- 10^9
        tera(13),    -- 10^12
        peta(14),    -- 10^15
        exa(15),     -- 10^18
        zetta(16),   -- 10^21
        yotta(17)    -- 10^24
    }

SmartmonSensorPrecision ::= TEXTUAL-CONVENTION
    STATUS      current
    DESCRIPTION
        "Number of decimal places in the fractional part of the
         associated SmartmonSensorValue fixed-point number.
         Positive values (1..9) indicate fractional digits.
         Negative values (-8..-1) indicate the number of accurate
         integer digits.  Zero means the value is not fixed-point.

         Example: temperature reported as whole degrees Celsius uses
         scale units(9) and precision 0.  A sensor reporting tenths of
         a degree uses precision 1 and a value ten times larger."
    REFERENCE "RFC 3433, EntitySensorPrecision"
    SYNTAX Integer32 (-8..9)

SmartmonSensorValue ::= TEXTUAL-CONVENTION
    STATUS      current
    DESCRIPTION
        "A sensor reading.  The true value is:
             reading * 10^(scale_exponent - precision)
         The value -1000000000 indicates underflow; +1000000000
         indicates overflow."
    REFERENCE "RFC 3433, EntitySensorValue"
    SYNTAX Integer32 (-1000000000..1000000000)

SmartmonSensorStatus ::= TEXTUAL-CONVENTION
    STATUS      current
    DESCRIPTION
        "Operational status of a sensor.
         ok(1)             -- agent can read the sensor value
         unavailable(2)    -- value temporarily unavailable
         nonoperational(3) -- sensor is believed to be broken"
    REFERENCE "RFC 3433, EntitySensorStatus"
    SYNTAX INTEGER {
        ok(1),
        unavailable(2),
        nonoperational(3)
    }

SmartmonLogicalBlockAddress ::= TEXTUAL-CONVENTION
    DISPLAY-HINT "d"
    STATUS      current
    DESCRIPTION
        "A 64-bit Logical Block Address (LBA) identifying a sector on a
         storage device.  Counter64 is used as the base type because
         SMIv2 provides no unsigned 64-bit integer; the counter
         semantics do not apply.  A value of 0xFFFFFFFFFFFFFFFF may
         indicate an unknown or invalid LBA depending on context."
    SYNTAX Counter64

END
